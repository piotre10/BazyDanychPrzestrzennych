FME workspace ex3.fmw

Parameters:
- SourceDataset_SHAPEFILE = C:\Users\Piotr\Desktop\bdline_essh_gb\Data\GB\scotland_and_wales_region.shp   # Source Esri Shapefile(s)
- SourceDataset_TIFF = ""C:\Users\Piotr\Desktop\ras250_gb\ras250_gb\data\HP.tif" "C:\Users\Piotr\Desktop\ras250_gb\ras250_gb\data\HT.tif" "C:\Users\Piotr\Desktop\ras250_gb\ras250_gb\data\HU.tif" "C:\Users\Piotr\Desktop\ras250_gb\ras250_gb\data\HW.tif" "C:\Users\Piotr\Desktop\ras250_gb\ras250_gb\data\HX.tif" "C:\Users\Piotr\Desktop\ras250_gb\ras250_gb\data\HY.tif" "C:\Users\Piotr\Desktop\ras250_gb\ras250_gb\data\HZ.tif" "C:\Users\Piotr\Desktop\ras250_gb\ras250_gb\data\NA.tif" "C:\Users\Piotr\Desktop\ras250_gb\ras250_gb\data\NB.tif" "C:\Users\Piotr\Desktop\ras250_gb\ras250_gb\data\NC.tif" "C:\Users\Piotr\Desktop\ras250_gb\ras250_gb\data\ND.tif" "C:\Users\Piotr\Desktop\ras250_gb\ras250_gb\data\NF.tif" "C:\Users\Piotr\Desktop\ras250_gb\ras250_gb\data\NG.tif" "C:\Users\Piotr\Desktop\ras250_gb\ras250_gb\data\NH.tif" "C:\Users\Piotr\Desktop\ras250_gb\ras250_gb\data\NJ.tif" "C:\Users\Piotr\Desktop\ras250_gb\ras250_gb\data\NK.tif" "C:\Users\Piotr\Desktop\ras250_gb\ras250_gb\data\NL.tif" "C:\Users\Piotr\Desktop\ras250_gb\ras250_gb\data\NM.tif" "C:\Users\Piotr\Desktop\ras250_gb\ras250_gb\data\NN.tif" "C:\Users\Piotr\Desktop\ras250_gb\ras250_gb\data\NO.tif" "C:\Users\Piotr\Desktop\ras250_gb\ras250_gb\data\NR.tif" "C:\Users\Piotr\Desktop\ras250_gb\ras250_gb\data\NS.tif" "C:\Users\Piotr\Desktop\ras250_gb\ras250_gb\data\NT.tif" "C:\Users\Piotr\Desktop\ras250_gb\ras250_gb\data\NU.tif" "C:\Users\Piotr\Desktop\ras250_gb\ras250_gb\data\NW.tif" "C:\Users\Piotr\Desktop\ras250_gb\ras250_gb\data\NX.tif" "C:\Users\Piotr\Desktop\ras250_gb\ras250_gb\data\NY.tif" "C:\Users\Piotr\Desktop\ras250_gb\ras250_gb\data\NZ.tif" "C:\Users\Piotr\Desktop\ras250_gb\ras250_gb\data\OV.tif" "C:\Users\Piotr\Desktop\ras250_gb\ras250_gb\data\SC.tif" "C:\Users\Piotr\Desktop\ras250_gb\ras250_gb\data\SD.tif" "C:\Users\Piotr\Desktop\ras250_gb\ras250_gb\data\SE.tif" "C:\Users\Piotr\Desktop\ras250_gb\ras250_gb\data\SH.tif" "C:\Users\Piotr\Desktop\ras250_gb\ras250_gb\data\SJ.tif" "C:\Users\Piotr\Desktop\ras250_gb\ras250_gb\data\SK.tif" "C:\Users\Piotr\Desktop\ras250_gb\ras250_gb\data\SM.tif" "C:\Users\Piotr\Desktop\ras250_gb\ras250_gb\data\SN.tif" "C:\Users\Piotr\Desktop\ras250_gb\ras250_gb\data\SO.tif" "C:\Users\Piotr\Desktop\ras250_gb\ras250_gb\data\SP.tif" "C:\Users\Piotr\Desktop\ras250_gb\ras250_gb\data\SR.tif" "C:\Users\Piotr\Desktop\ras250_gb\ras250_gb\data\SS.tif" "C:\Users\Piotr\Desktop\ras250_gb\ras250_gb\data\ST.tif" "C:\Users\Piotr\Desktop\ras250_gb\ras250_gb\data\SU.tif" "C:\Users\Piotr\Desktop\ras250_gb\ras250_gb\data\SV.tif" "C:\Users\Piotr\Desktop\ras250_gb\ras250_gb\data\SW.tif" "C:\Users\Piotr\Desktop\ras250_gb\ras250_gb\data\SX.tif" "C:\Users\Piotr\Desktop\ras250_gb\ras250_gb\data\SY.tif" "C:\Users\Piotr\Desktop\ras250_gb\ras250_gb\data\SZ.tif" "C:\Users\Piotr\Desktop\ras250_gb\ras250_gb\data\TA.tif" "C:\Users\Piotr\Desktop\ras250_gb\ras250_gb\data\TF.tif" "C:\Users\Piotr\Desktop\ras250_gb\ras250_gb\data\TG.tif" "C:\Users\Piotr\Desktop\ras250_gb\ras250_gb\data\TL.tif" "C:\Users\Piotr\Desktop\ras250_gb\ras250_gb\data\TM.tif" "C:\Users\Piotr\Desktop\ras250_gb\ras250_gb\data\TQ.tif" "C:\Users\Piotr\Desktop\ras250_gb\ras250_gb\data\TR.tif" "C:\Users\Piotr\Desktop\ras250_gb\ras250_gb\data\TV.tif""   # Source TIFF (Tagged Image File Format) File(s)
- FEATURE_TYPES =   # TIFF Feature Types to Read
- DestDataset_POSTGIS = local_postgres   # Connection

Readers:
- SHAPEFILE_1: SHAPEFILE from $(SourceDataset_SHAPEFILE)
- TIFF_1: TIFF from $(SourceDataset_TIFF)

Writers:
- POSTGIS_1: POSTGIS to $(DestDataset_POSTGIS)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Drop Incoming Attributes
    AGGREGATE_TYPE = Homogeneous Collection (If Possible)
    MODE = Geometry - Assemble One Level
    SEP = ,
    AGGREGATE -> Reprojector
Reprojector
    DEST = LL-WGS84
    INTERPOLATION_TYPE_NAME = Nearest Neighbor
    RASTER_CELL_SIZE = Preserve Cells
    RASTER_TOLERANCE = 0.0
    REPROJECTED -> Clipper [CLIPPER]
TIFF (reader TIFF_1)
    -> Reprojector_2
Reprojector_2
    DEST = LL-WGS84
    INTERPOLATION_TYPE_NAME = Nearest Neighbor
    RASTER_CELL_SIZE = Preserve Cells
    RASTER_TOLERANCE = 0.0
    REPROJECTED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> RasterPropertyExtractor
RasterPropertyExtractor
    -> Exports (writer POSTGIS_1)
Exports (writer POSTGIS_1)
    attributes: _clipped char(3), _num_bands int8, _num_rows int8, _num_columns int8, _spacing_x float8, _spacing_y float8, _origin_x float8, _origin_y float8, _rotation_x float8, _rotation_y float8, _min_x float8, _min_y float8, _max_x float8, _max_y float8, _cell_origin_x float8, _cell_origin_y float8, _upper_left_x float8, _upper_left_y float8, _upper_right_x float8, _upper_right_y float8, _lower_right_x float8, _lower_right_y float8, _lower_left_x float8, _lower_left_y float8
